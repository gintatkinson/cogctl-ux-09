module ietf-layer0-types { yang-version 1.1; namespace "urn:ietf:params:xml:ns:yang:ietf-layer0-types"; prefix l0-types; organization "IETF CCAMP Working Group"; contact "WG Web: <https://datatracker.ietf.org/wg/ccamp/> WG List: <mailto:ccamp@ietf.org> Editor: Haomian Zheng <mailto:zhenghaomian@huawei.com> Editor: Young Lee <mailto:younglee.tx@gmail.com> Editor: Aihua Guo <mailto:aihuaguo.ietf@gmail.com> Editor: Victor Lopez <mailto:victor.lopez@nokia.com> Editor: Daniel King <mailto:d.king@lancaster.ac.uk>"; description "This module defines Optical Layer 0 types. This module provides groupings that can be applicable to Layer 0 Fixed Optical Networks (e.g., CWDM (Coarse Wavelength Division Multiplexing) and DWDM (Dense Wavelength Division Multiplexing)) and flexi-grid optical networks. Copyright (c) 2021 IETF Trust and the persons identified as authors of the code. All rights reserved. Redistribution and use in source and binary forms, with or without modification, is permitted pursuant to, and subject to the license terms contained in, the Simplified BSD License set forth in Section 4.c of the IETF Trust's Legal Provisions Relating to IETF Documents (https://trustee.ietf.org/license-info). This version of this YANG module is part of RFC 9093; see the RFC itself for full legal notices."; revision 2021-08-13 { description "Initial version"; reference "RFC 9093: A YANG Data Model for Layer 0 Types"; } typedef dwdm-n { type int16; description "The given value 'N' is used to determine the nominal central frequency. The nominal central frequency, 'f', is defined by: f = 193100.000 GHz + N x channel spacing (measured in GHz), where 193100.000 GHz (193.100000 THz) is the ITU-T 'anchor frequency' for transmission over the DWDM grid, and where 'channel spacing' is defined by the dwdm-ch-spc-type."; reference "RFC6205: Generalized Labels for Lambda-Switch-Capable (LSC) Label Switching Routers, ITU-T G.694.1 (10/2020): Spectral grids for WDM applications: DWDM frequency grid"; } typedef cwdm-n { type int16; description "The given value 'N' is used to determine the nominal central wavelength. The nominal central wavelength is defined by: Wavelength = 1471 nm + N x channel spacing (measured in nm) where 1471 nm is the conventional 'anchor wavelength' for transmission over the CWDM grid, and where 'channel spacing' is defined by the cwdm-ch-spc-type."; reference "RFC 6205: Generalized Labels for Lambda-Switch-Capable (LSC) Label Switching Routers, ITU-T G.694.2 (12/2003): Spectral grids for WDM applications: CWDM wavelength grid"; } typedef flexi-n { type int16; description "The given value 'N' is used to determine the nominal central frequency. The nominal central frequency, 'f', is defined by: f = 193100.000 GHz + N x channel spacing (measured in GHz), where 193100.000 GHz (193.100000 THz) is the ITU-T 'anchor frequency' for transmission over the DWDM grid, and where 'channel spacing' is defined by the flexi-ch-spc-type. Note that the term 'channel spacing' can be substituted by the term 'nominal central frequency granularity' defined in clause 8 of ITU-T G.694.1."; reference "RFC 7698: Framework and Requirements for GMPLS-Based Control of Flexi-Grid Dense Wavelength Division Multiplexing (DWDM) Networks, ITU-T G.694.1 (10/2020): Spectral grids for WDM applications: DWDM frequency grid"; } typedef flexi-m { type uint16; description "The given value 'M' is used to determine the slot width. A slot width is defined by: slot width = M x SWG (measured in GHz), where SWG is defined by the flexi-slot-width-granularity."; reference "RFC 7698: Framework and Requirements for GMPLS-Based Control of Flexi-Grid Dense Wavelength Division Multiplexing (DWDM) Networks. ITU-T G.694.1 (10/2020): Spectral grids for WDM applications: DWDM frequency grid"; } identity l0-grid-type { description "Layer 0 grid type"; reference "RFC 6163: Framework for GMPLS and Path Computation Element (PCE) Control of Wavelength Switched Optical Networks (WSONs), ITU-T G.694.1 (10/2020): Spectral grids for WDM applications: DWDM frequency grid, ITU-T G.694.2 (12/2003): Spectral grids for WDM applications: CWDM wavelength grid"; } identity flexi-grid-dwdm { base l0-grid-type; description "Flexi-grid"; reference "RFC 7698: Framework and Requirements for GMPLS-Based Control of Flexi-Grid Dense Wavelength Division Multiplexing (DWDM) Networks, ITU-T G.694.1 (10/2020): Spectral grids for WDM applications: DWDM frequency grid"; } identity wson-grid-dwdm { base l0-grid-type; description "DWDM grid"; reference "RFC 6163:Framework for GMPLS and Path Computation Element (PCE) Control of Wavelength Switched Optical Networks (WSONs), ITU-T G.694.1 (10/2020): Spectral grids for WDM applications: DWDM frequency grid"; } identity wson-grid-cwdm { base l0-grid-type; description "CWDM grid"; reference "RFC 6205: Generalized Labels for Lambda-Switch-Capable (LSC) Label Switching Routers, ITU-T G.694.2 (12/2003): Spectral grids for WDM applications: CWDM wavelength grid"; } identity dwdm-ch-spc-type { description "DWDM channel-spacing type"; reference "RFC 6205: Generalized Labels for Lambda-Switch-Capable (LSC) Label Switching Routers, ITU-T G.694.1 (10/2020): Spectral grids for WDM applications: DWDM frequency grid"; } identity dwdm-100ghz { base dwdm-ch-spc-type; description "100 GHz channel spacing"; } identity dwdm-50ghz { base dwdm-ch-spc-type; description "50 GHz channel spacing"; } identity dwdm-25ghz { base dwdm-ch-spc-type; description "25 GHz channel spacing"; } identity dwdm-12p5ghz { base dwdm-ch-spc-type; description "12.5 GHz channel spacing"; } identity flexi-ch-spc-type { description "Flexi-grid channel-spacing type"; reference "RFC 7698: Framework and Requirements for GMPLS-Based Control of Flexi-Grid Dense Wavelength Division Multiplexing (DWDM) Networks, ITU-T G.694.1 (10/2020): Spectral grids for WDM applications: DWDM frequency grid"; } identity flexi-ch-spc-6p25ghz { base flexi-ch-spc-type; description "6.25 GHz channel spacing"; } identity flexi-slot-width-granularity { description "Flexi-grid slot width granularity"; } identity flexi-swg-12p5ghz { base flexi-slot-width-granularity; description "12.5 GHz slot width granularity"; } identity cwdm-ch-spc-type { description "CWDM channel-spacing type"; reference "RFC 6205: Generalized Labels for Lambda-Switch-Capable (LSC) Label Switching Routers, ITU-T G.694.2 (12/2003): Spectral grids for WDM applications: CWDM wavelength grid"; } identity cwdm-20nm { base cwdm-ch-spc-type; description "20nm channel spacing"; } /* Groupings. */ grouping wson-label-start-end { description "The WSON label-start or label-end used to specify WSON label range."; choice grid-type { description "Label for DWDM or CWDM grid"; case dwdm { leaf dwdm-n { when "derived-from-or-self(../../../grid-type, \"wson-grid-dwdm\")" { description "Valid only when grid type is DWDM."; } type l0-types:dwdm-n; description "The central frequency of DWDM."; reference "RFC 6205: Generalized Labels for Lambda-Switch-Capable (LSC) Label Switching Routers"; } } case cwdm { leaf cwdm-n { when "derived-from-or-self(../../../grid-type, \"wson-grid-cwdm\")" { description "Valid only when grid type is CWDM."; } type l0-types:cwdm-n; description "Channel wavelength computing input."; reference "RFC 6205: Generalized Labels for Lambda-Switch-Capable (LSC) Label Switching Routers"; } } } reference "RFC 6205: Generalized Labels for Lambda-Switch-Capable (LSC) Label Switching Routers"; } grouping wson-label-hop { description "Generic label-hop information for WSON"; choice grid-type { description "Label for DWDM or CWDM grid"; case dwdm { choice single-or-super-channel { description "single or super channel"; case single { leaf dwdm-n { type l0-types:dwdm-n; description "The given value 'N' is used to determine the nominal central frequency."; } } case super { leaf-list subcarrier-dwdm-n { type l0-types:dwdm-n; description "The given values 'N' are used to determine the nominal central frequency for each subcarrier channel."; reference "ITU-T Recommendation G.694.1: Spectral grids for WDM applications: DWDM frequency grid"; } } } } case cwdm { leaf cwdm-n { type l0-types:cwdm-n; description "The given value 'N' is used to determine the nominal central wavelength."; reference "RFC 6205: Generalized Labels for Lambda-Switch-Capable (LSC) Label Switching Routers"; } } } reference "RFC 6205: Generalized Labels for Lambda-Switch-Capable (LSC) Label Switching Routers"; } grouping l0-label-range-info { description "Information about Layer 0 label range."; leaf grid-type { type identityref { base l0-grid-type; } description "Grid type"; } leaf priority { type uint8; description "Priority in Interface Switching Capability Descriptor (ISCD)."; reference "RFC 4203: OSPF Extensions in Support of Generalized Multi-Protocol Label Switching (GMPLS)"; } reference "RFC 6205: Generalized Labels for Lambda-Switch-Capable (LSC) Label Switching Routers"; } grouping wson-label-step { description "Label step information for WSON"; choice l0-grid-type { description "Grid type: DWDM, CWDM, etc."; case dwdm { leaf wson-dwdm-channel-spacing { when "derived-from-or-self(../../grid-type, \"wson-grid-dwdm\")" { description "Valid only when grid type is DWDM."; } type identityref { base dwdm-ch-spc-type; } description "Label-step is the channel spacing (GHz), e.g., 100.000, 50.000, 25.000, or 12.500 GHz for DWDM."; reference "RFC 6205: Generalized Labels for Lambda-Switch-Capable (LSC) Label Switching Routers"; } } case cwdm { leaf wson-cwdm-channel-spacing { when "derived-from-or-self(../../grid-type, \"wson-grid-cwdm\")" { description "Valid only when grid type is CWDM."; } type identityref { base cwdm-ch-spc-type; } description "Label-step is the channel spacing (nm), i.e., 20 nm for CWDM, which is the only value defined for CWDM."; reference "RFC 6205: Generalized Labels for Lambda-Switch-Capable (LSC) Label Switching Routers"; } } } reference "RFC 6205: Generalized Labels for Lambda-Switch-Capable (LSC) Label Switching Routers, ITU-T G.694.2 (12/2003): Spectral grids for WDM applications: CWDM wavelength grid"; } grouping flexi-grid-label-start-end { description "The flexi-grid label-start or label-end used to specify flexi-grid label range."; leaf flexi-n { type l0-types:flexi-n; description "The given value 'N' is used to determine the nominal central frequency."; } reference "RFC 7698: Framework and Requirements for GMPLS-Based Control of Flexi-Grid Dense Wavelength Division Multiplexing (DWDM) Networks"; } grouping flexi-grid-frequency-slot { description "Flexi-grid frequency slot grouping."; uses flexi-grid-label-start-end; leaf flexi-m { type l0-types:flexi-m; description "The given value 'M' is used to determine the slot width."; } reference "RFC 7698: Framework and Requirements for GMPLS-Based Control of Flexi-Grid Dense Wavelength Division Multiplexing (DWDM) Networks"; } grouping flexi-grid-label-hop { description "Generic label-hop information for flexi-grid"; choice single-or-super-channel { description "single or super channel"; case single { uses flexi-grid-frequency-slot; } case super { list subcarrier-flexi-n { key "flexi-n"; uses flexi-grid-frequency-slot; description "List of subcarrier channels for flexi-grid super channel."; } } } reference "RFC 7698: Framework and Requirements for GMPLS-Based Control of Flexi-Grid Dense Wavelength Division Multiplexing (DWDM) Networks"; } grouping flexi-grid-label-range-info { description "Flexi-grid-specific label range related information"; uses l0-label-range-info; container flexi-grid { description "flexi-grid definition"; leaf slot-width-granularity { type identityref { base flexi-slot-width-granularity; } default "flexi-swg-12p5ghz"; description "Minimum space between slot widths. Default is 12.500 GHz."; reference "RFC 7698: Framework and Requirements for GMPLS-Based Control of Flexi-Grid Dense Wavelength Division Multiplexing (DWDM) Networks"; } leaf min-slot-width-factor { type uint16 { range "1..max"; } default "1"; description "A multiplier of the slot width granularity, indicating the minimum slot width supported by an optical port. Minimum slot width is calculated by: Minimum slot width (GHz) = min-slot-width-factor * slot-width-granularity."; reference "RFC 8363: GMPLS OSPF-TE Extensions in Support of Flexi- Grid Dense Wavelength Division Multiplexing (DWDM) Networks"; } leaf max-slot-width-factor { type uint16 { range "1..max"; } must '. >= ../min-slot-width-factor' { error-message "Maximum slot width must be greater than or equal to minimum slot width."; } description "A multiplier of the slot width granularity, indicating the maximum slot width supported by an optical port. Maximum slot width is calculated by: Maximum slot width (GHz) = max-slot-width-factor * slot-width-granularity If specified, maximum slot width must be greater than or equal to minimum slot width. If not specified, maximum slot width is equal to minimum slot width."; reference "RFC 8363: GMPLS OSPF-TE Extensions in Support of Flexi- Grid Dense Wavelength Division Multiplexing (DWDM) Networks"; } } } grouping flexi-grid-label-step { description "Label step information for flexi-grid"; leaf flexi-grid-channel-spacing { type identityref { base flexi-ch-spc-type; } default "flexi-ch-spc-6p25ghz"; description "Label-step is the nominal central frequency granularity (GHz), e.g., 6.25 GHz."; reference "RFC 7699: Generalized Labels for the Flexi-Grid in Lambda Switch Capable (LSC) Label Switching Routers"; } leaf flexi-n-step { type uint8; description "This attribute defines the multiplier for the supported values of 'N'. For example, given a grid with a nominal central frequency granularity of 6.25 GHz, the granularity of the supported values of the nominal central frequency could be 12.5 GHz. In this case, the values of flexi-n should be even and this constraint is reported by setting the flexi-n-step to 2. This attribute is also known as central frequency granularity in RFC 8363."; reference "RFC 8363: GMPLS OSPF-TE Extensions in Support of Flexi-Grid Dense Wavelength Division Multiplexing (DWDM) Networks"; } } }
